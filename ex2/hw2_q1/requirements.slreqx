# requirements

## Car Green1: Car light gets green. (Functional)
When the car's light was red for 60 ticks, it gets green and release a signal shows that light should get green.

## Car Green2: Car light stays green. (Functional)
When the car's light was green for less than 60 ticks, It stays green and increases the tick.

## Car Pending1: Car light enters 'Pending' state. (Functional)
When the car's light was green for less than 60 ticks, if a pedestrian pushed the pedestrian button, the light stayes green and enters the 'Pending' state and waits there until it reaches 60 ticks.

## Car Pending2: Car light stays on 'Pending' state. (Functional)
When the car's light is on 'Pending' state, if it hasn't reached 60 ticks yet, it stays on this state and increases tick.

## Car Yellow1: Car light gets yellow after 'Green' state. (Functional)
When the car's light was on 'Green' state for 60 ticks (or higher), if a pedestrian pushed the pedestrian button, it gets yellow and release a signal that shows that light should get yellow.

## Car Yellow2: Car light gets Yellow after 'Pending' state. (Functional)
When the car's light was on 'Pending' for 60 ticks (or higher), it gets yellow and release a signal that shows that light should get yellow.

## Car Yellow3: Car light stays yellow. (Functional)
When the car's light was yellow for less than 5 ticks, It stays green and increases the tick.

## Car Red1: Car light gets red. (Functional)
When the car's light was yellow for 5 ticks, it gets red and release a signal that shows that light should get red.

## Car Red2: Car light stays red. (Functional)
When the car's light was red for less than 60 ticks, It stays red and increases the tick.

## Pedestrian Red: Pedestrian light gets red. (Functional)
When the pedestrian light was green for 60 ticks, it gets red and release a signal shows that it should get red.

## Pedestrian Green1: Pedestrian light stays green. (Functional)
When the Pedestrian light was green for less than 60 ticks, it stays green and increases the tick.

## Pedestrian Green2: Pedestrian light gets green. (Functional)
Whenever the car's light gets red, the pedestrian light gets green and release a signal shows that it should get red.

## Pedestrian and Car light Conflict1: Both pedestrain's and car's light should never be green at the same time. (Informational)

## Pedestrian and Car light Conflict2: While car's light is yellow, pedestrian's light should never be green (Informational)

## Pedestrian and Car light Conflict3: While Car's light is on 'Pending' state, pedestrian's light should never be green. (Informational)

## Pedestrian Button Hit: Pedestrain light should be turn green when pedestrian button be hit. (Informational)

## Security: No out-system actor can change the functionality of the lights. (Informational)
